# Isolated FreeCAD GUI entry point. Only reviewed synthetic phases are accepted.
import datetime
import json
import os
from pathlib import Path
import sys
import traceback

try:
    from PySide import QtCore
except ImportError:
    try:
        from PySide6 import QtCore
    except ImportError:
        from PySide2 import QtCore

ROOT = Path(os.environ['DOM_REPO_ROOT']).resolve()
PHASE = os.environ['DOM_PHASE']
if PHASE not in {'build', 'cold-reopen', 'mutate', 'native-tools', 'restore-reopen'}:
    raise ValueError('Unapproved phase')
OUT = ROOT / 'build/smoke'
OUT.mkdir(parents=True, exist_ok=True)
TARGET = OUT / ('report.json' if PHASE == 'build' else PHASE + '.json')


def execute():
    code = 1
    report = {'status': 'FAILED', 'source': 'SYNTHETIC_ONLY', 'phase': PHASE,
              'pid': os.getpid(), 'invocation_id': os.environ['DOM_INVOCATION_ID'],
              'head_sha': os.environ['GITHUB_SHA'], 'construction_ready': False,
              'timestamp_utc': datetime.datetime.now(datetime.timezone.utc).isoformat()}
    try:
        import FreeCAD as App
        version = '.'.join(App.Version()[:3])
        report['version'] = version
        if version != '1.1.4':
            raise ValueError('Pinned FreeCAD 1.1.4 required')
        sys.path.insert(0, str(ROOT / 'ci'))
        import native_suite
        report.update(native_suite.run(PHASE))
        report['status'] = 'PASS'
        code = 0
    except Exception:
        report['traceback'] = traceback.format_exc()
    finally:
        try:
            import FreeCAD as App
            for name in list(App.listDocuments()):
                App.closeDocument(name)
        except Exception:
            pass
        TARGET.write_text(json.dumps(report, indent=2), encoding='utf-8')
        print('DOM_NATIVE_REPORT', json.dumps(report))
        QtCore.QCoreApplication.exit(code)


QtCore.QTimer.singleShot(0, execute)
